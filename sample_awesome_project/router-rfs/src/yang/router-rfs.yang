module router-rfs {

  namespace "http://example.com/router-rfs";
  prefix router-rfs;

  import ietf-inet-types {
    prefix inet;
  }
  import tailf-common {
    prefix tailf;
  }
  import tailf-ncs {
    prefix ncs;
  }

  description
    "Small rfs package for demonstration purposes";

  revision 2023-02-08 {
    description
      "Awesome NetDevOps demo";
  }

  list access-list-router-rfs {
    description "RFS utilities for Cisco IOS provisioning";
    uses ncs:service-data;
    ncs:servicepoint access-list-router-rfs-servicepoint;

    key "device";

    leaf device {
      tailf:info "Cisco IOS device";
      tailf:cli-expose-key-name;
      type leafref {
        path "/ncs:devices/ncs:device/ncs:name";
      }
      mandatory true;
    }

    list access_list {
      tailf:info "New Access-list";
      key "id";

      leaf id {
        tailf:info "Access-list ID";
        type string;
      }

      leaf action {
        tailf:info "Access type enumeration";
        type enumeration {
          enum "permit";
          enum "deny";
        }
        mandatory true;
      }

      leaf destination {
        tailf:info "Destination IP address";
        type inet:ipv4-address;
        mandatory true;
      }
    }
  }
}
